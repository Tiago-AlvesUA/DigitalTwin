-- Draft 05.10.2023
-- @brief Specification of the maneuver Coordination Message ETSI TS 103 561
-- - git SHA @todo
-- - git tag @todo
-- - Latest version available at @url https://forge.etsi.org/rep/ITS/MCM_TS103561

MCM-PDU-Descriptions {
    itu-t (0) identified-organization (4) etsi (0) itsDomain (5) wg1 (1) ts(103561) mcm (1) major-version-1 (1) minor-version-1 (1)
}

DEFINITIONS AUTOMATIC TAGS ::= 

BEGIN

IMPORTS
    --@brief Include ETSI TS 102 894-2
    --Include references from @url
    -- https://forge.etsi.org/rep/ITS/ITS_ASN1/blob/master/CDD_TS102894-2/ITS-Container.asn
    ItsPduHeader,
    Heading, DeltaReferencePosition, Speed, DriveDirection, LongitudinalAcceleration, LateralAcceleration, VerticalAcceleration, StationType, AltitudeValue, ConfidenceLevel, EuVehicleCategoryCode, SpecialTransportType, TimestampIts, Wgs84Angle, laneCount, lanePosition, intersectionTimeofPositionEntry, intersectionTimeofPositionLeaving
    FROM ETSI-ITS-CDD {itu-t (0) identified-organization (4) etsi (0) itsDomain (5) wg1 (1) ts (102894) cdd (2) major-version-3 (3) minor-version-1 (1)};

-- maneuver Coordination Block:

/**
 * This type represents the maneuver Coordination Block at a given facility.  
 *
 * It shall include the following components: 
 *
 * @field header: the header of the MCM PDU,
 * @field mcm: the payload of the MCM PDU,
*/

MCM ::= SEQUENCE {
    header ItsPduHeader,
    payload WrappedMcmInformationBlocks
}

WrappedMcmInformationBlocks ::= SEQUENCE {
    basicContainer McmBasicContainer,
    mcmContainer McmContainer
}
/**
* This DF represents a list of MCM information blocks, each with their type identifier.
*/

McmBasicContainer::= SEQUENCE {
    generationDeltaTime TimestampIts, -- Generation TimestampIts represent an integer value in milliseconds since 2004-01-01T00-00-00-00Z as defined in ETSI TS 102 894-2
    stationType StationType,
    deltaReferencePosition DeltaReferencePosition
}
    
McmContainer::= CHOICE {
    vehiclemaneuverContainer VehiclemaneuverContainer,
    acknowledgmentContainer AcknowledgmentContainer
    --advisedmaneuverContainer AdvisedmaneuverContainer
}

VehiclemaneuverContainer::= SEQUENCE {
    mcmType McmType,
    maneuverId ManeuverId,
    maneuverCoordinationConcept ManeuverCoordinationConcept,
    maneuverCoordinationRational ManeuverCoordinationRational,
    maneuverExecutionStatus ManeuverExecutionStatus,
    vehicleCurrentState VehicleCurrentState,
    trajectoryId TrajectoryId,
    vehicleTrajectory CHOICE {
        --frenetTrajectory FrenetTrajectory,
        wgs84Trajectory Wgs84Trajectory
    },
    maneuverAdviceContainer ManeuverAdviceContainer OPTIONAL
}


McmType::= ENUMERATED {intent (0), request (1), response (2), reservation (3), termination (4), cancellationRequest (5), emergencymaneuverReservation (6), executionStatus (7),offer (8), ack(9)
}

ManeuverId::= INTEGER (0..256) -- Unique identifier of the maneuver

ManeuverCoordinationConcept::= ENUMERATED {agreementSeeking (0), prescriptive (1)
}

ManeuverCoordinationRational::= CHOICE {
    maneuverCooperationGoal ManeuverCooperationGoal,
    maneuverCooperationCost ManeuverCooperationCost
}

ManeuverCooperationGoal ::= ENUMERATED {vehicleInterception (0), roadSafety (1), humanHelth (2), emergencyIntervention (3), roadOperatorIntervention (4), localTrafficManagement (5), globalTrafficManagement (6)
}

ManeuverCooperationCost ::= INTEGER { zero(0), oneThousndth(1) } (-1000..1000)

ManeuverExecutionStatus::= ENUMERATED {started (0), inProgress (1), completed (2), terminated (3), chained (4)
}

VehicleCurrentState::= SEQUENCE {
    mcmGenericCurrentState McmGenericCurrentState,
    vehicleAutomationState VehicleAutomationState,
    speed Speed,
    heading Heading,
    longitudinalAcceleration LongitudinalAcceleration,
    vehicleSize VehicleSize
}

McmGenericCurrentState::= SEQUENCE {
    mcmType McmType,
    maneuverId ManeuverId,
    maneuverCoordinationConcept ManeuverCoordinationConcept,
    maneuverCoordinationRational ManeuverCoordinationRational, 
    maneuverExecutionStatus ManeuverExecutionStatus
}

VehicleAutomationState::= SEQUENCE {
    humanDrivingLongitudinalAutomated BOOLEAN,
    humanDrivenLateralAutomated BOOLEAN,
    automatedDriving BOOLEAN DEFAULT FALSE -- 0: humanDriving, 1: automatedDriving
}

VehicleSize::= SEQUENCE {
    vehicleLenth INTEGER (0..65535), -- in meters
    vehicleWidth INTEGER (0..65535)  -- in meters
}

ReferenceCoordinatesSystem::= BOOLEAN -- 0: WGS84, 1: Frenet

TrajectoryId::= INTEGER (0..65535)

-- FrenetTrajectory::= SEQUENCE {
--     intermediatePoints SEQUENCE SIZE (1..10) OF IntermediatePoint
--     longitudinalPositions SEQUENCE SIZE (1..11) OF Polynom
--     lateralPositions SEQUENCE SIZE (1..11) OF Polynom
--     elevationPositions SEQUENCE SIZE (1..11) OF Polynom OPTIONAL
--     headings SEQUENCE SIZE (1..11) OF Polynom OPTIONAL
--     speed INTEGER (0..511)  in meters per second
-- }

IntermediatePoint::= CHOICE {
    reference IntermediatePointReference,
    lane IntermediatePointLane,
    intersection IntermediatePointIntersection,
    offroad IntermediatePointOffroad
}

-- Polynom ::= SEQUENCE {
--     coefficients SEQUENCE SIZE (1..6) OF PolygonCoefficient
--     start PolygonStartX
--     end PolygonEndX
--     xOffset PolygonXOffset
-- }

ReferenceStartingPosition ::= SEQUENCE {
    latitude                     Latitude,
    longitude                    Longitude,
    positionConfidenceEllipse    PositionConfidenceEllipse,
    altitude                     Altitude
}

IntermediatePointReference::= SEQUENCE {
    referenceStartingPosition ReferenceStartingPosition,
    referenceHeading Heading,
    lane Lane,
    timeOfPos TimeOfPos
}

IntermediatePointLane::= SEQUENCE {
    lane Lane,
    reason Reason,
    timeOfPos TimeOfPos
}

IntermediatePointIntersection::= SEQUENCE {
    exitLane SEQUENCE {
        lanePosition LanePosition,
        laneCount LaneCount
    },
    exitHeading Heading,
    timeOfPosEntry TimeOfPos, -- time on the trajectory when the intersection will be entered
    timeOfPosExit TimeOfPos -- time on the trajectory when the intersection will be leaved
}

IntermediatePointOffroad::= SEQUENCE {
    referencePosition ReferencePosition,
    referenceHeading Heading,
    timeOfPos TimeOfPos
}

Lane::= SEQUENCE {
    lanePosition LanePosition,
    laneCount LaneCount --total number of lanes at the position
}

PolynomCoefficient ::= REAL
PolynomStartX ::= INTEGER (0..2097151) -- Unit: 0.001 meter or seconds
PolynomEndX::= INTEGER (0..2097151) -- Unit: 0.001 meter or seconds
PolynomXOffst::= INTEGER (-8000000..8000000) -- Unit: 0.001 meter or seconds

-- Basic types
LaneCount::= INTEGER (1..16) -- Number of Lanes
TimeOfPos::= INTEGER (0..65535) -- Unit: 0.01 seconds

Reason::= ENUMERATED {
    none (0),
    laneOpening (1),
    laneClosing (2),
    laneChange (3)
}

Wgs84Trajectory ::= SEQUENCE {
    trajectoryPoints SEQUENCE SIZE(1..10) OF Wgs84TrajectoryPoint
}

Wgs84TrajectoryPoint ::= SEQUENCE {
    intermediatePoint IntermediatePoint,
    longitudePosition Longitude,
    latitudePosition Latitude,
    altitudePosition Altitude OPTIONAL,
    headings Heading OPTIONAL,
    speed Speed
}

ManeuverAdviceContainer ::= SEQUENCE {
    numberOfExecutants INTEGER (0..16),
    maneuver Maneuvers
}

Maneuvers ::= SEQUENCE SIZE (1..16) OF Maneuver

Maneuver::= SEQUENCE {
    itsId ItsId,
    currentStateAdvisedChange CurrentStateAdvisedChange,
    numberOfSubmaneuvers INTEGER (0..16),
    submaneuver Submaneuvers
}

Submaneuvers ::= SEQUENCE SIZE (1..16) OF Submaneuver

ItsId ::= INTEGER

AcknowledgmentContainer ::= SEQUENCE {
    acknowledgedType McmType,
    generationDeltaTime TimestampIts
}

Submaneuver::= SEQUENCE {
    submaneuverId INTEGER (0..16),
    referenceCoordinateSystem ReferenceCoordinatesSystem,
    advisedTrajectory BOOLEAN
    --advisedTRR TRR OPTIONAL,
    --temporalCharacteristics TemporalCharacteristics OPTIONAL,
    --kinematicsCharacteristics KinematicsCharacteristics OPTIONAL
}

CurrentStateAdvisedChange ::= INTEGER (0..11) -- 0: NO CHANGE, 1: TRANSIT TO HUMAN DRIVING MODE, 2: TRANSIT TO AUTOMATED DRIVING MODE, 3: FOLLOW ME, 4: JOIN GROUP, 5: LEAVE GROUP, 6: EMERGENCY BRAKE TRIGGERING, 7: STAY IN LANE, 8: RESET STOP, 9: RESET STAY IN LANE, 10: STAY AWAY OF VEHICLE WITH STATION ID, 11: RESET STAY AWAY

ManeuverResponse ::= CHOICE {
    offerAcceptation NULL,
    offerDecline NULL,
    requestAcceptation NULL,
    requestDecline RequestDecline
}

RequestDecline ::= ENUMERATED {agreementSeekingUnknown(0), agreementSeekingUnwanted (2), allUnableToConform (1), allUnableToUnderstand (3), allErroneousBehaviourDetected (4), allMissbehaviourDetected(5)}

END
