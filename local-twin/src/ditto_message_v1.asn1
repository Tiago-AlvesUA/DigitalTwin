DITTO-MSG DEFINITIONS AUTOMATIC TAGS ::= 
BEGIN

-- TYPES ================================================

Int8    ::= INTEGER (-128..127)
UInt8   ::= INTEGER (0..255)
Int16   ::= INTEGER (-32768..32767)
UInt16  ::= INTEGER (0..65535)
Int32   ::= INTEGER (-2147483648..2147483647)
UInt32  ::= INTEGER (0..4294967295)

-- Main DITTO-MSG structure ================================================

DITTO-MSG ::= SEQUENCE {
    topic   UTF8String,
    headers SEQUENCE {},
    path    UTF8String,
    value   ValueBody
}

DTM ::= SEQUENCE {
    header ItsPduHeader
    dtmBody DTMBody
}

ValueBody ::= SEQUENCE {
    referencePosition  RefPos,
    modemStatus        ModStat,
    nrModemStatus     NRModStat,
    lteModemStatus    LTEModStat,
    body                Body,
    esBrokerDelay     EsBrokerDelay,
    esBrokerThroughput EsBrokerThroughput
}

RefPos ::= SEQUENCE {
    properties  SEQUENCE {
        latitude    Int32,
        longitude   Int32,
        altitude    Int32
    }
}

ModStat ::= SEQUENCE {
    properties SEQUENCE {
        mcc     UInt16,
        mnc     UInt16
    }
}

NRModStat ::= SEQUENCE {
    properties  SEQUENCE {
        rsrp        Int16,
        rsrq        Int16,
        snr         Int16,
        pci         UInt16
    }
}

LTEModStat ::= SEQUENCE {
    properties  SEQUENCE {
        rsrp        Int16,
        rsrq        Int8,
        snr         Int16,
        pci         UInt16,
        rssi        Int8
    }
}

Body ::= SEQUENCE {
    properties          SEQUENCE {
        generationDeltaTime UInt32, -- Unsigned long
        sequenceNumber      INTEGER
    }
}

EsBrokerDelay ::= SEQUENCE {
    properties          SEQUENCE {
        messageDelay   INTEGER
    }
}

EsBrokerThroughput ::= SEQUENCE {
    properties          SEQUENCE {
        rxBytes        INTEGER,
        txBytes        INTEGER
    }
}
END
