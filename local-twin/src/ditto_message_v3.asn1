-- Descriptions é para integrar no repositório ASN do it2s...
--DTM-PDU-Descriptions {

--}

DITTO-STRUCT DEFINITIONS AUTOMATIC TAGS ::= 
BEGIN

-- IMPORTS ================================================

IMPORTS 
ItsPduHeader, TimestampIts, SequenceNumber, ReferencePosition FROM ETSI-ITS-CDD {
    itu-t (0) identified-organization (4) etsi (0) itsDomain (5) wg1 (1) 102894 cdd (2) major-version-4 (4) minor-version-1 (1)
} ModemStatus FROM ModemStatus-PDU-Descriptions {
    itu (0) it2s (1722) modemstatus(122) version (2)
};

-- TYPES ================================================

Int8    ::= INTEGER (-128..127)
UInt8   ::= INTEGER (0..255)
Int16   ::= INTEGER (-32768..32767)
UInt16  ::= INTEGER (0..65535)
Int32   ::= INTEGER (-2147483648..2147483647)
UInt32  ::= INTEGER (0..4294967295)

-- Main DITTO message structure ================================================

DITTO-STRUCT ::= SEQUENCE {
    topic   UTF8String,
    headers SEQUENCE {},
    path    UTF8String,
    value   Value --Can i change value to dtm?
}

Value ::= SEQUENCE {
    header ItsPduHeader, -- protocolVersion*, messageId*, stationId*
    dtm    DTM
}

DTM ::= SEQUENCE {
    referenceTime TimestampIts,
    sequenceNumber SequenceNumber,
    referencePosition ReferencePosition, 
    modemStatus ModemStatus OPTIONAL,
    networkLogs NetworkLogs OPTIONAL
}

NetworkLogs ::= SEQUENCE {
    messageDelay   INTEGER,
    messageThroughput EsBrokerThroughput
}

EsBrokerThroughput ::= SEQUENCE {
    rxBytes        INTEGER,
    txBytes        INTEGER
}    

END
