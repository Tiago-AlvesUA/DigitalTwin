ModemStatus-PDU-Descriptions {
    itu (0) it2s (1722) modemstatus(122) version (2)
}

DEFINITIONS AUTOMATIC TAGS ::=
BEGIN

ModemStatus ::= SEQUENCE {
	mcc 	INTEGER,
	mnc	INTEGER,
	ratMode	INTEGER,
	nr	NrModemStatus	OPTIONAL,
	lte 	LteModemStatus	OPTIONAL
}

NrModemStatus ::= SEQUENCE {
    rsrq INTEGER,
    rsrp INTEGER,
    snr INTEGER,
    pci INTEGER
}

LteModemStatus ::= SEQUENCE {
    rsrq INTEGER,
    rsrp INTEGER,
    rssi INTEGER,
    snr INTEGER,
    pci INTEGER
}

END
